#This code helps in getting a visualisation of the nesting done from the python code.

#NOTE: You need to delete the sheet once and undo (ctrl + Z) it to see the other shapes. 
#This is the bug of FreeCAD where the bigger object always comes in front of the other objects irrespective of their placement.

#Import the library files
import FreeCAD,Draft
import PartDesign
import PartDesignGui
import Spreadsheet
from math import sin,cos,degrees,radians,pi,sqrt,asin

#Create a new document and activate PartDesign Workbench
App.newDocument("Shape")
Gui.activateWorkbench("PartDesignWorkbench")
App.activeDocument().addObject('PartDesign::Body','Body')
Gui.activeView().setActiveObject('pdbody', App.activeDocument().Body)
Gui.Selection.clearSelection()
Gui.Selection.addSelection(App.ActiveDocument.Body)
App.ActiveDocument.recompute()
#Enter the length and width of sheet over here
sheet_length = 100.0
sheet_width = 110.0
sheet = [(0.0, 0.0, 0), (sheet_length, 0.0, 0), (sheet_length, sheet_width, 0), (0.0, sheet_width, 0)]
wire = Draft.makeWire(sheet, closed=True)

#Put the coordinates of the shapes over here by labelling all of them separately.
a=[(9.66, 1.0, 0), (18.32, 6.0, 0), (18.32, 16.0, 0), (9.66, 21.0, 0), (1.0, 16.0, 0), (1.0, 6.0, 0)]
b= [(19.32, 1.0, 0), (19.32, 16.0, 0), (34.32, 16.0, 0), (34.32, 1.0, 0)]
c=[(38.41, 1.0, 0), (48.41, 1.0, 0), (51.5, 10.51, 0), (43.41, 16.38, 0), (35.32, 10.51, 0)]
d= [(52.5, 1.0, 0), (62.5, 1.0, 0), (57.5, 4.16, 0)]
e= [(16.0, 52.0, 0), (16.26, 52.0, 0), (16.52, 51.99, 0), (16.79, 51.98, 0), (17.05, 51.96, 0), (17.31, 51.94, 0), (17.57, 51.92, 0), (17.83, 51.89, 0), (18.09, 51.85, 0), (18.35, 51.82, 0), (18.6, 51.77, 0), (18.86, 51.72, 0), (19.12, 51.67, 0), (19.37, 51.62, 0), (19.63, 51.55, 0), (19.88, 51.49, 0), (20.13, 51.42, 0), (20.39, 51.34, 0), (20.64, 51.27, 0), (20.88, 51.18, 0), (21.13, 51.1, 0), (21.38, 51.0, 0), (21.62, 50.91, 0), (21.86, 50.81, 0), (22.1, 50.7, 0), (22.34, 50.59, 0), (22.58, 50.48, 0), (22.81, 50.37, 0), (23.04, 50.24, 0), (23.27, 50.12, 0), (23.5, 49.99, 0), (23.73, 49.86, 0), (23.95, 49.72, 0), (24.17, 49.58, 0), (24.39, 49.44, 0), (24.6, 49.29, 0), (24.82, 49.14, 0), (25.03, 48.98, 0), (25.23, 48.82, 0), (25.44, 48.66, 0), (25.64, 48.49, 0), (25.84, 48.32, 0), (26.04, 48.15, 0), (26.23, 47.97, 0), (26.42, 47.79, 0), (26.61, 47.61, 0), (26.79, 47.42, 0), (26.97, 47.23, 0), (27.15, 47.04, 0), (27.32, 46.84, 0), (27.49, 46.64, 0), (27.66, 46.44, 0), (27.82, 46.23, 0), (27.98, 46.03, 0), (28.14, 45.82, 0), (28.29, 45.6, 0), (28.44, 45.39, 0), (28.58, 45.17, 0), (28.72, 44.95, 0), (28.86, 44.73, 0), (28.99, 44.5, 0), (29.12, 44.27, 0), (29.24, 44.04, 0), (29.37, 43.81, 0), (29.48, 43.58, 0), (29.59, 43.34, 0), (29.7, 43.1, 0), (29.81, 42.86, 0), (29.91, 42.62, 0), (30.0, 42.38, 0), (30.1, 42.13, 0), (30.18, 41.88, 0), (30.27, 41.64, 0), (30.34, 41.39, 0), (30.42, 41.13, 0), (30.49, 40.88, 0), (30.55, 40.63, 0), (30.62, 40.37, 0), (30.67, 40.12, 0), (30.72, 39.86, 0), (30.77, 39.6, 0), (30.82, 39.35, 0), (30.85, 39.09, 0), (30.89, 38.83, 0), (30.92, 38.57, 0), (30.94, 38.31, 0), (30.96, 38.05, 0), (30.98, 37.79, 0), (30.99, 37.52, 0), (31.0, 37.26, 0), (31.0, 37.0, 0), (31.0, 36.74, 0), (30.99, 36.48, 0), (30.98, 36.21, 0), (30.96, 35.95, 0), (30.94, 35.69, 0), (30.92, 35.43, 0), (30.89, 35.17, 0), (30.85, 34.91, 0), (30.82, 34.65, 0), (30.77, 34.4, 0), (30.72, 34.14, 0), (30.67, 33.88, 0), (30.62, 33.63, 0), (30.55, 33.37, 0), (30.49, 33.12, 0), (30.42, 32.87, 0), (30.34, 32.61, 0), (30.27, 32.36, 0), (30.18, 32.12, 0), (30.1, 31.87, 0), (30.0, 31.62, 0), (29.91, 31.38, 0), (29.81, 31.14, 0), (29.7, 30.9, 0), (29.59, 30.66, 0), (29.48, 30.42, 0), (29.37, 30.19, 0), (29.24, 29.96, 0), (29.12, 29.73, 0), (28.99, 29.5, 0), (28.86, 29.27, 0), (28.72, 29.05, 0), (28.58, 28.83, 0), (28.44, 28.61, 0), (28.29, 28.4, 0), (28.14, 28.18, 0), (27.98, 27.97, 0), (27.82, 27.77, 0), (27.66, 27.56, 0), (27.49, 27.36, 0), (27.32, 27.16, 0), (27.15, 26.96, 0), (26.97, 26.77, 0), (26.79, 26.58, 0), (26.61, 26.39, 0), (26.42, 26.21, 0), (26.23, 26.03, 0), (26.04, 25.85, 0), (25.84, 25.68, 0), (25.64, 25.51, 0), (25.44, 25.34, 0), (25.23, 25.18, 0), (25.03, 25.02, 0), (24.82, 24.86, 0), (24.6, 24.71, 0), (24.39, 24.56, 0), (24.17, 24.42, 0), (23.95, 24.28, 0), (23.73, 24.14, 0), (23.5, 24.01, 0), (23.27, 23.88, 0), (23.04, 23.76, 0), (22.81, 23.63, 0), (22.58, 23.52, 0), (22.34, 23.41, 0), (22.1, 23.3, 0), (21.86, 23.19, 0), (21.62, 23.09, 0), (21.38, 23.0, 0), (21.13, 22.9, 0), (20.88, 22.82, 0), (20.64, 22.73, 0), (20.39, 22.66, 0), (20.13, 22.58, 0), (19.88, 22.51, 0), (19.63, 22.45, 0), (19.37, 22.38, 0), (19.12, 22.33, 0), (18.86, 22.28, 0), (18.6, 22.23, 0), (18.35, 22.18, 0), (18.09, 22.15, 0), (17.83, 22.11, 0), (17.57, 22.08, 0), (17.31, 22.06, 0), (17.05, 22.04, 0), (16.79, 22.02, 0), (16.52, 22.01, 0), (16.26, 22.0, 0), (16.0, 22.0, 0), (15.74, 22.0, 0), (15.48, 22.01, 0), (15.21, 22.02, 0), (14.95, 22.04, 0), (14.69, 22.06, 0), (14.43, 22.08, 0), (14.17, 22.11, 0), (13.91, 22.15, 0), (13.65, 22.18, 0), (13.4, 22.23, 0), (13.14, 22.28, 0), (12.88, 22.33, 0), (12.63, 22.38, 0), (12.37, 22.45, 0), (12.12, 22.51, 0), (11.87, 22.58, 0), (11.61, 22.66, 0), (11.36, 22.73, 0), (11.12, 22.82, 0), (10.87, 22.9, 0), (10.62, 23.0, 0), (10.38, 23.09, 0), (10.14, 23.19, 0), (9.9, 23.3, 0), (9.66, 23.41, 0), (9.42, 23.52, 0), (9.19, 23.63, 0), (8.96, 23.76, 0), (8.73, 23.88, 0), (8.5, 24.01, 0), (8.27, 24.14, 0), (8.05, 24.28, 0), (7.83, 24.42, 0), (7.61, 24.56, 0), (7.4, 24.71, 0), (7.18, 24.86, 0), (6.97, 25.02, 0), (6.77, 25.18, 0), (6.56, 25.34, 0), (6.36, 25.51, 0), (6.16, 25.68, 0), (5.96, 25.85, 0), (5.77, 26.03, 0), (5.58, 26.21, 0), (5.39, 26.39, 0), (5.21, 26.58, 0), (5.03, 26.77, 0), (4.85, 26.96, 0), (4.68, 27.16, 0), (4.51, 27.36, 0), (4.34, 27.56, 0), (4.18, 27.77, 0), (4.02, 27.97, 0), (3.86, 28.18, 0), (3.71, 28.4, 0), (3.56, 28.61, 0), (3.42, 28.83, 0), (3.28, 29.05, 0), (3.14, 29.27, 0), (3.01, 29.5, 0), (2.88, 29.73, 0), (2.76, 29.96, 0), (2.63, 30.19, 0), (2.52, 30.42, 0), (2.41, 30.66, 0), (2.3, 30.9, 0), (2.19, 31.14, 0), (2.09, 31.38, 0), (2.0, 31.62, 0), (1.9, 31.87, 0), (1.82, 32.12, 0), (1.73, 32.36, 0), (1.66, 32.61, 0), (1.58, 32.87, 0), (1.51, 33.12, 0), (1.45, 33.37, 0), (1.38, 33.63, 0), (1.33, 33.88, 0), (1.28, 34.14, 0), (1.23, 34.4, 0), (1.18, 34.65, 0), (1.15, 34.91, 0), (1.11, 35.17, 0), (1.08, 35.43, 0), (1.06, 35.69, 0), (1.04, 35.95, 0), (1.02, 36.21, 0), (1.01, 36.48, 0), (1.0, 36.74, 0), (1.0, 37.0, 0), (1.0, 37.26, 0), (1.01, 37.52, 0), (1.02, 37.79, 0), (1.04, 38.05, 0), (1.06, 38.31, 0), (1.08, 38.57, 0), (1.11, 38.83, 0), (1.15, 39.09, 0), (1.18, 39.35, 0), (1.23, 39.6, 0), (1.28, 39.86, 0), (1.33, 40.12, 0), (1.38, 40.37, 0), (1.45, 40.63, 0), (1.51, 40.88, 0), (1.58, 41.13, 0), (1.66, 41.39, 0), (1.73, 41.64, 0), (1.82, 41.88, 0), (1.9, 42.13, 0), (2.0, 42.38, 0), (2.09, 42.62, 0), (2.19, 42.86, 0), (2.3, 43.1, 0), (2.41, 43.34, 0), (2.52, 43.58, 0), (2.63, 43.81, 0), (2.76, 44.04, 0), (2.88, 44.27, 0), (3.01, 44.5, 0), (3.14, 44.73, 0), (3.28, 44.95, 0), (3.42, 45.17, 0), (3.56, 45.39, 0), (3.71, 45.6, 0), (3.86, 45.82, 0), (4.02, 46.03, 0), (4.18, 46.23, 0), (4.34, 46.44, 0), (4.51, 46.64, 0), (4.68, 46.84, 0), (4.85, 47.04, 0), (5.03, 47.23, 0), (5.21, 47.42, 0), (5.39, 47.61, 0), (5.58, 47.79, 0), (5.77, 47.97, 0), (5.96, 48.15, 0), (6.16, 48.32, 0), (6.36, 48.49, 0), (6.56, 48.66, 0), (6.77, 48.82, 0), (6.97, 48.98, 0), (7.18, 49.14, 0), (7.4, 49.29, 0), (7.61, 49.44, 0), (7.83, 49.58, 0), (8.05, 49.72, 0), (8.27, 49.86, 0), (8.5, 49.99, 0), (8.73, 50.12, 0), (8.96, 50.24, 0), (9.19, 50.37, 0), (9.42, 50.48, 0), (9.66, 50.59, 0), (9.9, 50.7, 0), (10.14, 50.81, 0), (10.38, 50.91, 0), (10.62, 51.0, 0), (10.87, 51.1, 0), (11.12, 51.18, 0), (11.36, 51.27, 0), (11.61, 51.34, 0), (11.87, 51.42, 0), (12.12, 51.49, 0), (12.37, 51.55, 0), (12.63, 51.62, 0), (12.88, 51.67, 0), (13.14, 51.72, 0), (13.4, 51.77, 0), (13.65, 51.82, 0), (13.91, 51.85, 0), (14.17, 51.89, 0), (14.43, 51.92, 0), (14.69, 51.94, 0), (14.95, 51.96, 0), (15.21, 51.98, 0), (15.48, 51.99, 0), (15.74, 52.0, 0)]

#These are the wires created for the coordinates of the shapes the user has entered above.
wire = Draft.makeWire(a, closed=True)
wire = Draft.makeWire(b, closed=True)
wire = Draft.makeWire(c, closed=True)
wire = Draft.makeWire(d, closed=True)
wire = Draft.makeWire(e, closed=True)
wire = Draft.makeWire(f, closed=True)
wire = Draft.makeWire(g, closed=True)
wire = Draft.makeWire(h, closed=True)
wire = Draft.makeWire(i, closed=True)
wire = Draft.makeWire(j, closed=True)
wire= Draft.makeWire(k, closed=True)
wire= Draft.makeWire(l, closed=True)
wire= Draft.makeWire(m, closed=True)
wire= Draft.makeWire(n, closed=True)
wire= Draft.makeWire(o, closed=True)
wire= Draft.makeWire(p, closed=True)
wire= Draft.makeWire(q, closed=True)
wire= Draft.makeWire(r, closed=True)
wire= Draft.makeWire(s, closed=True)
wire= Draft.makeWire(t, closed=True)
wire= Draft.makeWire(u, closed=True)
wire= Draft.makeWire(v, closed=True)
wire= Draft.makeWire(w, closed=True)
wire= Draft.makeWire(x, closed=True)
wire= Draft.makeWire(y, closed=True)
wire= Draft.makeWire(z, closed=True)
wire= Draft.makeWire(a1, closed=True)
wire= Draft.makeWire(a2, closed=True)
wire= Draft.makeWire(a3, closed=True)
wire= Draft.makeWire(a4, closed=True)
